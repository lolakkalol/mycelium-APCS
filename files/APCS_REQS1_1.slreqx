# APCS_REQS1_1

## APCS_REQS1.1!Sheet2: References to APCS_REQS1.1.xlsx (Sheet2) (Container)
Read-only references to Microsoft Excel document.

### APCS-REQ-001: The APCS shall be able to collect sensor data (Functional)

### APCS-REQ-002: The APCS shall be able to convert sensor data to attitude values (Functional)

### APCS-REQ-003: The APCS shall be able to communicate with the CDHS (Functional)

### APCS-REQ-004: The APCS shall be able to receive thrust command (Functional)

### APCS-REQ-005: The APCS shall be able to receive attitude command (Functional)

### APCS-REQ-006: The APCS shall reach the desired attitude within {x time units} (Functional)

### APCS-REQ-007: The APCS shall be able to compare the desired attitude to its actual attitude (Functional)

### APCS-REQ-008: The APCS shall reach the desired position within {x time units} (Functional)

### APCS-REQ-009: The APCS shall be able to detect anomalies in thrust control (Functional)

### APCS-REQ-010: If anomalies in thrust control are detected, the APCS shall inform the user (Functional)

### APCS-REQ-011: The APCS shall be able to detect anomalies in attitude control (Functional)

### APCS-REQ-012: If anomalies in attitude control are detected, the APCS shall inform the user (Functional)

### APCS-REQ-014: The APCS shall be able to sense the completion of commands (Functional)

### APCS-REQ-015: The APCS shall inform the user of the completion of commands (Functional)

### APCS-REQ-016: The APCS shall be able to receive health check request (Functional)

### APCS-REQ-017: The APCS shall be able to distribute health check request to its sub-system (Functional)

### APCS-REQ-018: The APCS shall be able to conduct individual sub-systems health check (Functional)

### APCS-REQ-019: The APCS shall be able to detect when the systems health is non-acceptable (Functional)

### APCS-REQ-020: The APCS shall be able to collect the health results from all sub-systems within the APCS (Functional)

### APCS-REQ-021: The APCS shall be able to receive software updates (Functional)

### APCS-REQ-022: The APCS shall be able to recognize which functions shall be updated (Functional)

### APCS-REQ-023: While the APCS updates its software, the APCS shall keep execution of affected functionalities paused (Functional)

### APCS-REQ-024: When the APCS has finished its software update the APCS shall continue execution of affected functionalities (Functional)

### APCS-REQ-025: The APCS shall be able to update software within {x time units} after receiving the software update (Functional)

### APCS-REQ-026: The APCS shall be able to check if software is correctly updated (Functional)

### APCS-REQ-028: If the software is not updated correctly, the APCS shall inform the user (Functional)

### APCS-REQ-029: If the software is not updated correctly, the APCS shall disregard the software update and resume to the previous version (Functional)

### APCS-REQ-030: When the APCS software update is accepted, then the APCS shall resume the paused functionalities (Functional)

### APCS-REQ-031: The APCS shall be able to be enabled (Functional)

### APCS-REQ-032: The APCS shall be able to be disabled (Functional)

### APCS-REQ-033: The APCS shall control if the command is within reasonable value (Functional)

### APCS-REQ-034: If the command is outside reasonable values, the APCS shall inform the user (Functional)

### APCS-REQ-035: The APCS shall be made of material that shall burn up when reentering the atmosphere (Functional)

### APCS-REQ-036: The total mass of the APCS shall not exceed 4 kg (Functional)

### APCS-REQ-037: The dimensions of the APCS shall be 100x100x200 mm (Functional)

### APCS-REQ-038: If the command is outside reasonable values, then APCS shall not execute the command (Functional)

### APCS-REQ-039: The APCS shall be able to execute commands received from ground station (Functional)

### APCS-REQ-040: The APCS shall be able to activate its propulsion (Functional)

### APCS-REQ-041: The APCS shall be able to classify the received information (Functional)

### APCS-DEP-REQ-001: When receiving a command to dissable the SanityCheck the APCS shall bypass all sanity checks for commands (Functional)

### APCS-DEP-REQ-002: The APCS sub-systems shall detect missing messages (Functional)

### APCS-DEP-REQ-003: The APCS sub-systems shall detect received corrupt messages (Functional)

### APCS-DEP-REQ-004: If the APCS tries to overwrite the update service, THEN the APCS shall be prevented from doing so (Functional)

### APCS-DEP-REQ-005: While de-tumbling the APCS shall disable the de-orbit function (Functional)

### APCS-DEP-REQ-006: If the ThrusterControl is acting erroneously, THEN the APCS shall inhibit the use of thrusters (Functional)
