# APCS_REQ

## APCS-REQ!Blad1: References to APCS-REQ.xlsx (Blad1) (Container)
Read-only references to Microsoft Excel document.

### APCS-REQ-001: The system shall be able to determine its own attitude (Functional)

### APCS-REQ-002: The system shall be able to change its orbit (Functional)

### APCS-REQ-003: The system shall be able to de-orbit at the end of its mission lifetime (Functional)

### APCS-REQ-004: The system shall be able to de-tumble after launch (Functional)

### APCS-REQ-005: The system shall be able to control its attitude (Functional)

### APCS-REQ-006: When the system is inside the launcher, the system shall be disabled according to launch specifications (Functional)

### APCS-REQ-007: The CubeSat shall be able to update the software of its sub-systems (Functional)

### APCS-REQ-008: The CubeSat shall be able to check that a software update was installed and works as expected (Functional)

### APCS-REQ-009: The CubeSat shall be able to monitor system's health status (Functional)

### APCS-REQ-010: When the CubeSat receives a command from the ground station, the CubeSat shall be able to determine if the command is safe to execute (Functional)

### APCS-REQ-011: When the CubeSat receives a command from the ground station, the CubeSat shall be able to execute the command (Functional)

### APCS-REQ-012: If the CubeSat is able to perform the recieved command, then the CubeSat shall notify the sender of the command that it succeeded to perform the command (Functional)

### APCS-REQ-013: The CubeSat shall be able to prevent the execution of a non-safe command recieved from the ground station (Functional)

### APCS-REQ-014: The CubeSat shall be able to control its thrust (Functional)

### APCS-REQ-015: The CubeSat shall be able to detect anomalies in thrust and attitude control while changing attitude (Functional)

### APCS-REQ-016: If changing orbit and an anomaly is detected, THEN the system shall notify the user (Functional)

### APCS-REQ-017: The CubeSat shall be able to determine its attitude (Functional)

### APCS-REQ-018: The CubeSat shall recognise the command to change orbit (Functional)

### APCS-REQ-019: The CubeSat shall recognise the command to de-orbit (Functional)

### APCS-REQ-020: The CubeSat shall recognise the command to change attitude (Functional)

### APCS-REQ-021: The CubeSat shall be made of materials that can burn up when reentering the atmosphere (Functional)

### APCS-REQ-022: The CubeSat shall be able to counteract and neutralise the change in attitude induced by being launched (Functional)

### APCS-REQ-023: If changing the attitude and an anomaly is detected, THEN the CubeSat shall notify the user (Functional)

### APCS-REQ-024: The CubeSat shall be able to notify the user of the completion of its attitude change (Functional)

### APCS-REQ-025: If the CubeSat is not able to perform the recieved command, then the CubeSat shall notify the sender of the command that it failed to perform the command (Functional)
